"""Fixed launcher for the pinned FreeCADCmd BIM worker."""

import sys
from pathlib import Path

sys.dont_write_bytecode = True
sys.path.insert(0, str(Path(__file__).resolve().parents[2]))

from book_production_platform.bim_production.worker import main

main(sys.argv)
